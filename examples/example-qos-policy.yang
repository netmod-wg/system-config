module example-qos-policy {
  yang-version 1.1;
  namespace "urn:example:qos";
  prefix "qos";

  container qos-policies {
    list policy {
      key "name";
      leaf name {
        type string;
      }
      list queue {
        key "queue-id";
        leaf queue-id {
          type int32 {
          range "1..32";
          }
        }
        leaf maximum-burst-size {
          type int32 {
            range "0..100";
          }
        }
      }
    }
  }
}
