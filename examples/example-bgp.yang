module example-bgp {
  yang-version 1.1;
  namespace "urn:example:bgp";
  prefix "ex-bgp";

  import ietf-inet-types {
    prefix "inet";
  }

  container bgp {
    leaf local-as {
      type inet:as-number;
    }
    leaf peer-as {
      type inet:as-number;
    }
    list peer {
      key "address";
      leaf address {
        type inet:ip-address;
      }
      leaf local-as {
        type inet:as-number;
        description
          "... Defaults to ../local-as.";
      }
      leaf peer-as {
        type inet:as-number;
        description
          "... Defaults to ../peer-as.";
      }
      leaf local-port {
        type inet:port-number;
      }
      leaf remote-port {
        type inet:port-number;
        default "179";
      }
      leaf state {
        config false;
        type enumeration {
          enum init;
          enum established;
          enum closing;
        }
      }
    }
  }
}
